module vyatta-op-show-bridge-v1 {
	namespace "urn:vyatta.com:mgmt:vyatta-op-show-bridge:1";
	prefix vyatta-op-show-bridge-v1;

	import vyatta-opd-extensions-v1 {
		prefix opd;
	}
	import vyatta-op-show-v1 {
		prefix show;
	}
	import vyatta-types-v1 {
		prefix types;
	}

	organization "AT&T Inc.";
	contact
		"AT&T
		 Postal: 208 S. Akard Street
		         Dallas, TX 25202
		 Web: www.att.com";

	description
		"Copyright (c) 2019, AT&T Intellectual Property.
		 All rights reserved.

		 Redistribution and use in source and binary forms, with or
		 without modification, are permitted provided that the following
		 conditions are met:

		 1. Redistributions of source code must retain the above copyright
			notice, this list of conditions and the following disclaimer.
		 2. Redistributions in binary form must reproduce the above
			copyright notice, this list of conditions and the following
			disclaimer in the documentation and/or other materials provided
			with the distribution.
		 3. Neither the name of the copyright holder nor the names of its
			contributors may be used to endorse or promote products derived
			from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		Defines the top-level 'bridge' node under 'show' for operational CLI";

	revision 2019-03-12 {
		description "Initial version";
	}

	opd:augment /show:show {
		opd:command bridge {
			opd:help "Show bridging information";
			opd:on-enter 'vyatta-bridge-op --action=show_bridge';

			opd:argument bridge-name {
				opd:help "Show bridge information for a given bridge";
				opd:on-enter 'vyatta-bridge-op --action=show_bridge --bridge="$3"';
				opd:allowed 'vyatta-interfaces.pl --show bridge --filter-out "\."';
				type string {
					pattern 'br[0-9]+';
					opd:pattern-help "<brN>";
				}

				opd:command macs {
					opd:help "Show bridge forwarding database";
					opd:on-enter 'vyatta-bridge-op --action=show_macs --bridge="$3"';

					opd:option mac-address {
						opd:help "Show specified MAC address from bridge forwarding database";
						opd:on-enter 'vyatta-bridge-op --action=show_macs --bridge="$3" --mac="$6"';
						type types:mac-address;
					}

					opd:option port {
						opd:help "Show bridge forwarding database for a given port";
						opd:on-enter 'vyatta-bridge-op --action=show_macs --bridge="$3" --port="$6"';
						opd:allowed 'vyatta-bridge-ports --bridge="$3" --show-ports';
						type types:interface-ifname;
					}
				}
			}
		}
	}
}
