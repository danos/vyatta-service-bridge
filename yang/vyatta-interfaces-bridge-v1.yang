module vyatta-interfaces-bridge-v1 {
	namespace "urn:vyatta.com:mgmt:vyatta-interfaces-bridge:1";
	prefix vyatta-interfaces-bridge-v1;

	import vyatta-interfaces-v1 {
		prefix if;
	}
	import vyatta-interfaces-dataplane-v1 {
		prefix interfaces-dataplane;
	}
	import vyatta-interfaces-tunnel-v1 {
		prefix interfaces-tunnel;
	}
	import vyatta-interfaces-bonding-v1 {
		prefix interfaces-bonding;
	}
	import vyatta-interfaces-l2tpeth-v1 {
		prefix interfaces-l2tpeth;
	}
	import vyatta-types-v1 {
		prefix types;
	}
	import configd-v1 {
		prefix configd;
	}
	import vyatta-interfaces-bridge-state-v1 {
		prefix br-state;
	}

	organization "Brocade Communications Systems, Inc.";
	contact
		"Brocade Communications Systems, Inc.
		 Postal: 130 Holger Way
		         San Jose, CA 95134
		 E-mail: support@Brocade.com
		 Web: www.brocade.com";

	description
		"Copyright (c) 2019, AT&T Intellectual Property.
		 All rights reserved.

		 Copyright (c) 2015-2016 by Brocade Communications Systems, Inc.
		 All rights reserved.

		 Redistribution and use in source and binary forms, with or
		 without modification, are permitted provided that the following
		 conditions are met:

		 1. Redistributions of source code must retain the above copyright
			notice, this list of conditions and the following disclaimer.
		 2. Redistributions in binary form must reproduce the above
			copyright notice, this list of conditions and the following
			disclaimer in the documentation and/or other materials provided
			with the distribution.
		 3. Neither the name of the copyright holder nor the names of its
			contributors may be used to endorse or promote products derived
			from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 The YANG module for vyatta-interfaces-bridge-v1";

	revision 2019-07-04 {
		description "Add multicast-router leaf to enable multicast forwarding on the bridge";
	}
	revision 2019-04-09 {
		description
			"Add bridge FDB summary state for each port. Provide a netconf RPC to
			 retrieve the complete forwarding database";
	}
	revision 2019-02-26 {
		description "Add bridge & port operational state to the interface";
	}
	revision 2016-03-28 {
		description "Remove use of bash in action scripts";
	}
	revision 2015-08-17 {
		description "Break out bridge-base grouping for use by VDR";
	}
	revision 2015-08-14 {
		description "Initial revision of version 1.";
	}

	grouping bridge-group {
		container bridge-group {
			presence "bridge specific parameters";
			description "Add this interface to a bridge group.";
			configd:priority "320";
			configd:help "Add this interface to a bridge group";
			configd:end "vyatta-bridge.pl ${COMMIT_ACTION} $VAR(../@)";

			leaf bridge {
				type string {
					pattern "v?br[0-9]+" {
						configd:error-message "$VAR(@): not a valid name for a bridge";
					}
				}
				mandatory true;
				description "Bridge group name.";
				configd:help "Bridge group name";
				configd:allowed "vyatta-interfaces.pl --show=bridge";
				configd:validate "/opt/vyatta/share/tmplscripts/bridge/configd_validate1.cli";
			}
		}
	}

	augment /if:interfaces/interfaces-dataplane:dataplane {
		uses bridge-group;
	}
	augment /if:interfaces/interfaces-tunnel:tunnel {
		uses bridge-group {
			refine bridge-group {
				configd:end "/opt/vyatta/share/tmplscripts/interfaces/tunnel/bridge-group/configd_end.sh";
			}
		}
	}
	augment /if:interfaces/interfaces-bonding:bonding {
		uses bridge-group;
	}
	augment /if:interfaces/interfaces-l2tpeth:l2tpeth/interfaces-l2tpeth:vif {
		uses bridge-group {
			refine bridge-group {
				configd:end "vyatta-bridge.pl ${COMMIT_ACTION} $VAR(../../@).$VAR(../@)";
			}
		}
	}
	augment /if:interfaces/interfaces-l2tpeth:l2tpeth {
		uses bridge-group;
	}
	augment /if:interfaces/interfaces-dataplane:dataplane/interfaces-dataplane:vif {
		uses bridge-group {
			refine bridge-group {
				configd:end "vyatta-bridge.pl ${COMMIT_ACTION} $VAR(../../@).$VAR(../@)";
			}
		}
	}
	augment /if:interfaces/interfaces-bonding:bonding/interfaces-bonding:vif {
		uses bridge-group {
			refine bridge-group {
				configd:end "vyatta-bridge.pl ${COMMIT_ACTION} $VAR(../../@).$VAR(../@)";
			}
		}
	}

	grouping bridge-base {
		leaf description {
			type if:description;
			description "Interface description.";
			configd:help "Interface description";
			configd:update "ip link set dev $VAR(../@) alias '$VAR(@)'";
			configd:delete "vyatta-interfaces.pl --dev=$VAR(../@) --delete-description";
		}
		leaf disable {
			type empty;
			description "Disable bridge interface.";
			configd:help "Disable bridge interface";
			configd:create "/opt/vyatta/share/tmplscripts/interfaces/bridge/disable/configd_create.sh";
		}
		leaf-list address {
			type if:address-dhcp;
			ordered-by "user";
			description "IP address.";
			configd:help "IP address";
			configd:create "vyatta-address add $VAR(../@) $VAR(@)";
			configd:allowed "echo 'dhcp dhcpv6 <>'";
		}
		leaf mac {
			type types:mac-address {
				configd:syntax "/opt/vyatta/share/tmplscripts/interfaces/bridge/mac/configd_syntax1.cli";
			}
			description "Media Access Control (MAC) address.";
			configd:help "Media Access Control (MAC) address";
			configd:create "vyatta-interfaces-bridge --action=set_mac --bridge=$VAR(../@) --val=$VAR(@)";
			configd:delete "vyatta-interfaces-bridge --action=del_mac --bridge=$VAR(../@) --val=$VAR(@)";
		}
		leaf multicast-router {
			type empty;
			description "Enable multicast forwarding";
			configd:help "Enable multicast forwarding";
			configd:create "vyatta-interfaces-bridge --action=set_multicast_router --bridge=$VAR(../@)";
			configd:delete "vyatta-interfaces-bridge --action=del_multicast_router --bridge=$VAR(../@)";
		}
		leaf aging {
			type uint32 {
				range "0|10..1000000";
			}
			default "300";
			description "Interval learnt MAC addresses are retained (0 for no aging).";
			configd:help "Interval learnt MAC addresses are retained (0 for no aging)";
			configd:update "vyatta-interfaces-bridge --action=set_ageing --bridge=$VAR(../@) --val=$VAR(@)";
		}
		container ip {
			description "IPv4 parameters.";
			configd:help "IPv4 parameters";
		}
		container ipv6 {
			presence "true";
			description "IPv6 parameters.";
			configd:help "IPv6 parameters";
		}
	}

	augment /if:interfaces {
		list bridge {
			configd:priority "310";
			configd:help "Bridge interface name";
			configd:create "/opt/vyatta/share/tmplscripts/interfaces/bridge/configd_create.sh";
			configd:delete "ip link del $VAR(@)";
			configd:end "/opt/vyatta/sbin/vyatta-intf-end $VAR(@)";
			key "tagnode";
			leaf tagnode {
				type string {
					length 3..15;
					pattern "br[0-9]+";
					configd:pattern-help "<brN>";
				}
				description "Bridge interface name.";
				configd:help "Bridge interface name";
			}

			uses bridge-base {
				refine address {
				       configd:priority "320";
				}
			}

			leaf disable-link-detect {
				type empty;
				description "Ignore link state changes.";
				configd:help "Ignore link state changes";
				configd:create "vyatta-link-detect $VAR(../@) off";
				configd:delete "vyatta-link-detect $VAR(../@) on";
			}
		}

		container bridge-state {
			config false;
			configd:get-state "vyatta-bridge-state";

			list bridges {
				description "State of all the bridges in the system";
				uses br-state:bridge-state-grp;
				key bridge-name;

				list interfaces {
					description "Member ports of this bridge";
					uses br-state:bridge-port-state-grp;
					key port-name;

					container forwarding-database-summary {
						description "MAC forwarding database summary";
						uses br-state:bridge-fdb-state-summary-grp;
					}
				}
			}
		}
	}

	rpc bridge-fdb {
		description
			"Retrieve the contents of the MAC forwarding database for the indicated
		     bridge interface";
		configd:call-rpc "vyatta-bridge-get-fdb";

		input {
			leaf bridge {
				description
					"Name of bridge interface to be queried";
				mandatory true;
				type string {
					length 3..15;
					pattern "br[0-9]+";
				}
			}
			leaf port-name {
				description
					"Name of bridge port to be queried";
				type types:interface-ifname;
			}
			leaf mac-address {
				description
					"Particular MAC address to be queried";
				type types:mac-address;
			}
		}
		output {
			uses br-state:bridge-fdb-state-grp;
		}
	}
}
